FME workspace GEOTIFF_to_PGRASTER.fmw

Parameters:
- DestDataset_POSTGIS_RASTER =
- SourceDataset_GEOTIFF =

Readers:
- GEOTIFF_1: GEOTIFF from $(SourceDataset_GEOTIFF) in CH1903Plus_1.LV95/01

Writers:
- POSTGIS_RASTER_1: POSTGIS_RASTER to $(DestDataset_POSTGIS_RASTER) in CH1903Plus_1.LV95/01

Note: Entree en GeoTIFF et sortie PGRaster
GEOTIFF (reader GEOTIFF_1)
    -> test_raster (writer POSTGIS_RASTER_1)
test_raster (writer POSTGIS_RASTER_1)
